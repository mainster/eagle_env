#usage "Add the characters in the word 'Hello'\n"
"Usage: RUN sample1.ulp"
// Definitions:
string hello = "Hello";
string s = path_epf[0] + '/' + "mylib.lbr";

int count(string s) {
	int c = 0;
	for (int i = 0; s[i]; ++i)
	c += s[i];
	return c;
}

// Statements:
/////////////////////////
output("sample1") {
	printf("Count is: %d\n", count(hello));
	printf("%s\n", s);
}


if (board) board(B) {
	output(filesetext(B.name, ".out")) {
	printf("%s\n", B.name);
	}
}
